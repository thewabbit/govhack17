FME workspace sqlite3_csv2_esrishape2csv2.fmw

Parameters:
- SourceDataset_SQLITE3 = $(FME_MF_DIR)output/results.sl3   # SQLite Database
- SourceDataset_CSV2 = $(FME_MF_DIR)output/Base_Index_Fair_and_above.csv   # Source CSV (Comma Separated Value) File(s)
- SourceDataset_ESRISHAPE = $(FME_MF_DIR)Data/kx-nz-meshblocks-2006-census-SHP.zip Folder/nz-meshblocks-2006-census.shp   # Source Esri Shapefile(s)
- SourceDataset_ESRISHAPE_3 = $(FME_MF_DIR)Data/Swimming_Water_Quality_Sites.zip Folder/Swimming_Water_Quality_Sites.shp   # Source Esri Shapefile(s)
- DestDataset_ESRISHAPE = $(FME_MF_DIR_USERTYPED)output\output.zip   # Destination Esri Shapefile Folder
- DestDataset_OGCKML = $(FME_MF_DIR)output/mb_w_data.kml   # Destination Google KML File

Readers:
- CSV2_1: CSV2 from $(SourceDataset_CSV2)
- ESRISHAPE_1: ESRISHAPE from $(SourceDataset_ESRISHAPE_3)
- SQLITE3_1: SQLITE3 from $(SourceDataset_SQLITE3)
- ESRISHAPE_2: ESRISHAPE from $(SourceDataset_ESRISHAPE)

Writers:
- ESRISHAPE_3: ESRISHAPE to $(DestDataset_ESRISHAPE)
- OGCKML_1: OGCKML to $(DestDataset_OGCKML)

Swimming_Water_Quality_Sites (reader ESRISHAPE_1)
    attributes: OBJECTID long, SITE_ID char(80), DISPLAY_NA char(80), AREA_CODE char(80), SHOW_ON_MA char(80), SITE_TYPE char(80), SITE_GRADE char(80), RAIN_AFFEC char(80), SITE_NOT_S char(80), WARNING_TE char(254), NOTE_TEXT char(80), DISPLAY_AR char(80), DISPLAY_GR char(80), DISPLAY_LI char(80), NZMGX number(24,15), NZMGY number(24,15), NZMS260 char(80), NZTMX number(24,15), NZTMY number(24,15), NZTOPO50 char(80), WGS84_LONG number(24,15), WGS84_LATI number(24,15), SOURCECODE char(80), QARCODE long, CREATEDBY char(80), CREATEDDAT char(80), MODIFIEDBY char(80), MODIFIEDDA char(80), SITE_SAMPL char(80)
    -> FeatureMerger_3 [SUPPLIER]
results (reader SQLITE3_1)
    attributes: url text, MB06 text, SITE_ID text, _response_body text, _http_status_code text, summary text, json_type text, json_index text
    -> FeatureMerger_3 [REQUESTOR]
FeatureMerger_3
    PROCESS_DUPS = Yes
    SUPPLIERS_FIRST = Yes
    GEOM_TYPE = Build Polygons
    ATTR_CONFLICT_RES = Use Requestor
    JOIN_KEYS = @Value(SITE_ID) @Value(SITE_ID) AUTO
    ATTR_ACCUM_MODE = Merge Supplier
    IGNORE_NULLS = No
    CONNECT_Z_MODE = First Wins
    REJECT_NULL_MISSING_KEYS = No
    MERGE_TYPE = Attributes Only
    MERGED -> JSONExtractor
JSONExtractor
    EXTRACT_QUERY_TABLE = distance json["distance"] time json["trafficTime"]
    JSON_DOCUMENT = @Value(summary)
    EVALUATED -> AttributeManager
AttributeManager
    ATTR_TABLE:
      REMOVE url
      REMOVE _response_body
      REMOVE _http_status_code
      REMOVE summary
      REMOVE json_type
      REMOVE json_index
    -> FeatureMerger [REQUESTOR]
CSV (reader CSV2_1)
    attributes: FID string, SITE_ID string, Base_index string
    -> FeatureMerger [SUPPLIER]
FeatureMerger
    PROCESS_DUPS = No
    SUPPLIERS_FIRST = Yes
    ATTR_CONFLICT_RES = Use Requestor
    JOIN_KEYS = @Value(SITE_ID) @Value(SITE_ID) AUTO
    ATTR_ACCUM_MODE = Merge Supplier
    IGNORE_NULLS = No
    REJECT_NULL_MISSING_KEYS = No
    MERGE_TYPE = Attributes Only
    MERGED -> AttributeManager_2
AttributeManager_2
    ATTR_TABLE:
      SET_TO distance = @Evaluate(@CurrentAttribute()/1000)
      SET_TO time = @Evaluate(@CurrentAttribute()/60)
      SET_TO rating = @Evaluate(@Value(Base_index)-(@Value(distance)/2))
    -> AttributeRounder
AttributeRounder
    PLACES = 0
    SRC_ATTRS = distance time
    ROUND_TYPE = Nearest
    -> FeatureMerger_2 [SUPPLIER]
nz-meshblocks-2006-census (reader ESRISHAPE_2)
    attributes: MB06 char(7), REGC06 char(2), CON06 char(4), MCON06 char(4), TA06 char(3), WARD06 char(5), CB06 char(5), TASUB06 char(5), AU06 char(6), UA06 char(3), GED02 char(3), MED02 char(1), TA06V2 char(3), WARD06V2 char(5), CB06V2 char(5), TASUB06V2 char(5)
    -> Tester
Note: test if canty
Tester
    BOOL_OP = AND
    TEST_CLAUSE:
      TEST @Value(REGC06) = 13
      TEST @Value(WARD06) NOT_= 99999
    TEST_MODE = Automatic
    TEST_DESCRIPTION = ""
    PASSED -> AttributeManager_4
AttributeManager_4
    ATTR_TABLE:
      REMOVE REGC06
      REMOVE CON06
      REMOVE MCON06
      REMOVE TA06
      REMOVE WARD06
      REMOVE CB06
      REMOVE TASUB06
      REMOVE AU06
      REMOVE UA06
      REMOVE GED02
      REMOVE MED02
      REMOVE TA06V2
      REMOVE WARD06V2
      REMOVE CB06V2
      REMOVE TASUB06V2
    -> FeatureMerger_2 [REQUESTOR]
FeatureMerger_2
    PROCESS_DUPS = No
    SUPPLIERS_FIRST = Yes
    LIST_NAME = results
    LIST_ATTRS_TO_INCLUDE = distance rating time DISPLAY_NA
    ATTR_CONFLICT_RES = Use Requestor
    JOIN_KEYS = @Value(MB06) @Value(MB06) AUTO
    ATTR_ACCUM_MODE = Merge Supplier
    IGNORE_NULLS = No
    REJECT_NULL_MISSING_KEYS = No
    MERGE_TYPE = Attributes Only
    MERGED -> ListSorter
    UNMERGED_REQUESTOR -> AttributeManager_5
ListSorter
    SRC_LIST = results{}.rating
    ORDER = Descending
    TYPE = Numeric
    -> AttributeManager_3
AttributeManager_3
    ATTR_TABLE:
      REMOVE distance
      REMOVE time
      REMOVE rating
      SET_TO Res0_Distance = @Value(results{0}.distance)
      SET_TO Res0_Time = @Value(results{0}.time)
      SET_TO Res0_Rating = @Value(results{0}.rating)
      SET_TO Res0_Name = @Value(results{0}.DISPLAY_NA)
      SET_TO Res1_Distance = @Value(results{1}.distance)
      SET_TO Res1_Time = @Value(results{1}.time)
      SET_TO Res1_Rating = @Value(results{1}.rating)
      SET_TO Res1_Name = @Value(results{1}.DISPLAY_NA)
      SET_TO Res2_Distance = @Value(results{2}.distance)
      SET_TO Res2_Time = @Value(results{2}.time)
      SET_TO Res2_Rating = @Value(results{2}.rating)
      SET_TO Res2_Name = @Value(results{2}.DISPLAY_NA)
      SET_TO popup_str
    -> TestFilter
TestFilter
    TEST_LIST:
      BOOL_OP,AND,COMPOSITE_TEST,<Unused>,TEST_CLAUSE,"TEST Res2_Distance ATTRIBUTE_IS_MISSING """"
      TEST Res1_Distance ATTRIBUTE_IS_MISSING """"",One,BOOL_OP,AND,COMPOSITE_TEST,<Unused>,TEST_CLAUSE,"TEST Res2_Distance ATTRIBUTE_IS_MISSING """"",Two
    DEFAULT_VALUE = Three
    One -> AttributeCreator
    Two -> AttributeCreator_2
    Three -> AttributeCreator_3
AttributeCreator
    ATTR_TABLE = SET_TO popup_str = <p>This area is @Value(Res0_Distance)km from the nearest swimable location, @Value(Res0_Name). It is approximatly a @Value(Res0_Time) minute drive.</p>
    -> TestFilter_Two
    -> AttributeManager_5
AttributeCreator_2
    ATTR_TABLE = SET_TO popup_str = <p>This area is @Value(Res0_Distance)km from the nearest swimable location, @Value(Res0_Name). It is approximatly a @Value(Res0_Time) minute drive. You may also like to check out the following location:</p><ul><li>@Value(Res1_Name) - @Value(Res1_Distance)km - @Value(Res1_Time) minutes</li></ul>
    -> TestFilter_Two
    -> AttributeManager_5
AttributeCreator_3
    ATTR_TABLE = SET_TO popup_str = <p>This area is @Value(Res0_Distance)km from the nearest swimable location, @Value(Res0_Name). It is approximatly a @Value(Res0_Time) minute drive. You may also like to check out the following locations:</p><ul><li>@Value(Res1_Name) - @Value(Res1_Distance)km - @Value(Res1_Time)</li><li>@Value(Res2_Name) - @Value(Res2_Distance)km - @Value(Res2_Time) minutes</li></ul>
    -> TestFilter_Two
    -> AttributeManager_5
AttributeManager_5
    ATTR_TABLE:
      RENAME_SET_VALUE Res0_Distance > Res0_Dista
      RENAME_SET_VALUE Res0_Rating > Res0_Ratin
      RENAME_SET_VALUE Res1_Rating > Res1_Ratin
      RENAME_SET_VALUE Res1_Distance > Res1_Dista
      RENAME_SET_VALUE Res2_Distance > Res2_Dista
      RENAME_SET_VALUE Res2_Rating > Res2_Ratin
      REMOVE FID
      REMOVE Base_index
      REMOVE results{}.distance
      REMOVE results{}.time
      REMOVE results{}.rating
      REMOVE OBJECTID
      REMOVE DISPLAY_NA
      REMOVE AREA_CODE
      REMOVE SHOW_ON_MA
      REMOVE SITE_TYPE
      REMOVE SITE_GRADE
      REMOVE RAIN_AFFEC
      REMOVE SITE_NOT_S
      REMOVE WARNING_TE
      REMOVE NOTE_TEXT
      REMOVE DISPLAY_AR
      REMOVE DISPLAY_GR
      REMOVE DISPLAY_LI
      REMOVE NZMGX
      REMOVE NZMGY
      REMOVE NZMS260
      REMOVE NZTMX
      REMOVE NZTMY
      REMOVE NZTOPO50
      REMOVE WGS84_LONG
      REMOVE WGS84_LATI
      REMOVE SOURCECODE
      REMOVE QARCODE
      REMOVE CREATEDBY
      REMOVE CREATEDDAT
      REMOVE MODIFIEDBY
      REMOVE MODIFIEDDA
      REMOVE SITE_SAMPL
      REMOVE results{}.DISPLAY_NA
    -> mb_w_data (writer ESRISHAPE_3)
    -> mb_w_data_kml (writer OGCKML_1)
mb_w_data (writer ESRISHAPE_3)
    attributes: popup_str char(1000), MB06 char(7), SITE_ID char(254), Res0_Dista char(200), Res0_Ratin char(200), Res0_Time char(200), Res0_Name char(200), Res1_Ratin char(200), Res1_Dista char(200), Res1_Time char(200), Res1_Name char(200), Res2_Dista char(200), Res2_Ratin char(200), Res2_Name char(200), Res2_Time char(200)
mb_w_data_kml (writer OGCKML_1)
    attributes: popup_str kml_char(2000), MB06 kml_char(7), SITE_ID kml_char(255), Res0_Dista kml_char(200), Res0_Ratin kml_char(200), Res0_Time kml_char(200), Res0_Name kml_char(200), Res1_Ratin kml_char(200), Res1_Dista kml_char(200), Res1_Time kml_char(200), Res1_Name kml_char(200), Res2_Dista kml_char(200), Res2_Ratin kml_char(200), Res2_Name kml_char(200), Res2_Time kml_char(200)
TestFilter_Two: Inspector
