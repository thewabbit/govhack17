FME workspace esrishape_esrishape2none.fmw

Parameters:
- apikey = G5t7Re1mgxWAa6MWeia9
- appcode = 2y-0mPdZ0QIoQ-qRrwvgMw
- SourceDataset_ESRISHAPE = $(FME_MF_DIR)Data/kx-nz-meshblocks-2006-census-SHP.zip Folder/nz-meshblocks-2006-census.shp   # Source Esri Shapefile(s)
- SourceDataset_ESRISHAPE_3 = $(FME_MF_DIR)Data/Swimming_Water_Quality_Sites.zip Folder/Swimming_Water_Quality_Sites.shp   # Source Esri Shapefile(s)
- DestDataset_SQLITE3 = $(FME_MF_DIR)output/results.sl3   # SQLite Database

Readers:
- ESRISHAPE_2: ESRISHAPE from $(SourceDataset_ESRISHAPE_3) in EPSG:4326
- ESRISHAPE_1: ESRISHAPE from $(SourceDataset_ESRISHAPE) in EPSG:2193

Writers:
- SQLITE3_1: SQLITE3 to $(DestDataset_SQLITE3)

Swimming_Water_Quality_Sites (reader ESRISHAPE_2)
    attributes: OBJECTID long, SITE_ID char(80), DISPLAY_NA char(80), AREA_CODE char(80), SHOW_ON_MA char(80), SITE_TYPE char(80), SITE_GRADE char(80), RAIN_AFFEC char(80), SITE_NOT_S char(80), WARNING_TE char(254), NOTE_TEXT char(80), DISPLAY_AR char(80), DISPLAY_GR char(80), DISPLAY_LI char(80), NZMGX number(24,15), NZMGY number(24,15), NZMS260 char(80), NZTMX number(24,15), NZTMY number(24,15), NZTOPO50 char(80), WGS84_LONG number(24,15), WGS84_LATI number(24,15), SOURCECODE char(80), QARCODE long, CREATEDBY char(80), CREATEDDAT char(80), MODIFIEDBY char(80), MODIFIEDDA char(80), SITE_SAMPL char(80)
    -> Reprojector
Reprojector
    SOURCE = Read from feature
    RASTER_CELL_SIZE = Preserve Cells
    INTERPOLATION_TYPE_NAME = Nearest Neighbor
    DEST = EPSG:2193
    REPROJECTED -> TestFilter
TestFilter
    TEST_LIST = BOOL_OP,OR,COMPOSITE_TEST,<Unused>,TEST_CLAUSE,"TEST @Value(SITE_TYPE) = Freshwater",Freshwater,BOOL_OP,OR,COMPOSITE_TEST,<Unused>,TEST_CLAUSE,"TEST @Value(SITE_TYPE) = Marine",Marine
    DEFAULT_VALUE = <UNFILTERED>
    Freshwater -> NeighborFinder [CANDIDATE]
nz-meshblocks-2006-census (reader ESRISHAPE_1)
    attributes: MB06 char(7), REGC06 char(2), CON06 char(4), MCON06 char(4), TA06 char(3), WARD06 char(5), CB06 char(5), TASUB06 char(5), AU06 char(6), UA06 char(3), GED02 char(3), MED02 char(1), TA06V2 char(3), WARD06V2 char(5), CB06V2 char(5), TASUB06V2 char(5)
    -> Tester
Note: test if canty
Tester
    TEST_DESCRIPTION = ""
    BOOL_OP = OR
    TEST_MODE = Automatic
    TEST_CLAUSE = TEST @Value(REGC06) = 13
    PASSED -> CenterPointReplacer
Note: get mid point
CenterPointReplacer
    MODE = Center of Gravity Point
    POINT -> CoordinateExtractor
CoordinateExtractor
    MODE = All Coordinates
    LIST_NAME = _indices
    -> AttributeCreator_2
AttributeCreator_2
    ATTR_TABLE:
      SET_TO nztm x = @Value(_indices{0}.x)
      SET_TO nztm y = @Value(_indices{0}.y)
    -> AttributeReprojector
AttributeReprojector
    YATTR = _indices{0}.y
    XATTR = _indices{0}.x
    SOURCE = EPSG:2193
    DEST = LL-WGS84
    -> AttributeCreator_3
AttributeCreator_3
    ATTR_TABLE:
      SET_TO lat = @Value(_indices{0}.y)
      SET_TO long = @Value(_indices{0}.x)
    -> NeighborFinder [BASE]
NeighborFinder
    TREAT_POLYGON_AS = Lines
    CLOSE_LIST_ATTRS_TO_INCLUDE = SITE_ID
    ATTR_ACCUM_MODE = Merge Candidate
    CLOSE_LIST_NAME = _candidates
    K = 10
    INSERT_VERTEX = No
    MODE = Bases and Candidates
    CLOSE_LIST_ATTRS_TO_INCLUDE_MODE = Selected Attributes
    MAX = 100000
    CANDIDATES_FIRST = Yes
    ATTR_CONFLICT_RES = Use Base
    MATCHED -> ListExploder
ListExploder
    ATTR_ACCUM_MODE = Merge List Attributes
    ATTR_CONFLICT_RES = Use List Attribute Values
    INDEX_ATTR = _element_index
    LIST_ATTR = _candidates{}
    ELEMENTS -> AttributeReprojector_2
AttributeReprojector_2
    YATTR = closest_candidate_y
    XATTR = closest_candidate_x
    SOURCE = EPSG:2193
    DEST = EPSG:4326
    -> AttributeCreator
AttributeCreator
    ATTR_TABLE = SET_TO url = https://route.cit.api.here.com/routing/7.2/calculateroute.json?app_id=$(apikey)&app_code=$(appcode)&waypoint0=geo!@Value(lat),@Value(long)&waypoint1=geo!@Value(closest_candidate_y),@Value(closest_candidate_x)&mode=fastest;car;traffic:disabled
    -> Decelerator
    -> AttributeCreator_Output
Decelerator
    DECEL_TYPE = Limit Features Per Second
    FEATURES_PER_SECOND = 30
    -> HTTPCaller
HTTPCaller
    CONNECTION_TIMEOUT_LENGTH = 60
    VERIFY_SSL_CERTIFICATES = Yes
    USE_COOKIES = No
    RESPONSE_HEADER_LIST_ATTR = _headers
    TRANSFER_TIMEOUT_LENGTH = 90
    TARGET_ATTR = _response_body
    FOLLOW_REDIRECTS = Yes
    TARGET_ATTR_ENCODING = auto-detect
    SAVE_FILE = Attribute
    ERROR_ATTR = _error
    TARGET_URL = @Value(url)
    STATUS_CODE_ATTR = _http_status_code
    HTTP_METHOD = GET
    -> AttributeManager
    <Rejected> -> failed_http_call (writer SQLITE3_1)
AttributeManager
    ATTR_TABLE:
      REMOVE lat
      REMOVE long
      REMOVE nztm x
      REMOVE nztm y
      REMOVE REGC06
      REMOVE CON06
      REMOVE MCON06
      REMOVE TA06
      REMOVE WARD06
      REMOVE CB06
      REMOVE TASUB06
      REMOVE AU06
      REMOVE UA06
      REMOVE GED02
      REMOVE MED02
      REMOVE TA06V2
      REMOVE WARD06V2
      REMOVE CB06V2
      REMOVE TASUB06V2
      REMOVE _indices{}.x
      REMOVE _indices{}.y
      REMOVE _indices{}.z
      REMOVE OBJECTID
      REMOVE DISPLAY_NA
      REMOVE AREA_CODE
      REMOVE SHOW_ON_MA
      REMOVE SITE_TYPE
      REMOVE SITE_GRADE
      REMOVE RAIN_AFFEC
      REMOVE SITE_NOT_S
      REMOVE WARNING_TE
      REMOVE NOTE_TEXT
      REMOVE DISPLAY_AR
      REMOVE DISPLAY_GR
      REMOVE DISPLAY_LI
      REMOVE NZMGX
      REMOVE NZMGY
      REMOVE NZMS260
      REMOVE NZTMX
      REMOVE NZTMY
      REMOVE NZTOPO50
      REMOVE WGS84_LONG
      REMOVE WGS84_LATI
      REMOVE SOURCECODE
      REMOVE QARCODE
      REMOVE CREATEDBY
      REMOVE CREATEDDAT
      REMOVE MODIFIEDBY
      REMOVE MODIFIEDDA
      REMOVE SITE_SAMPL
      REMOVE _distance
      REMOVE _angle
      REMOVE _candidate_angle
      REMOVE _candidate_label_angle
      REMOVE _closest_candidate_x
      REMOVE _closest_candidate_y
      REMOVE _closest_base_x
      REMOVE _closest_base_y
      REMOVE distance
      REMOVE angle
      REMOVE candidate_angle
      REMOVE candidate_label_angle
      REMOVE closest_candidate_x
      REMOVE closest_candidate_y
      REMOVE closest_base_x
      REMOVE closest_base_y
      REMOVE _element_index
      REMOVE _headers{}.name
      REMOVE _headers{}.value
      SET_TO summary = @Value(_response_body)
    -> JSONFragmenter_2
JSONFragmenter_2
    JSON_QUERY = json[*]["route"][0]["summary"]
    EXTRACT_ATTR = Yes
    JSON_ATTR = summary
    RECURSIVE = Yes
    FRAGMENTS -> HTTPCaller_Output
    FRAGMENTS -> results (writer SQLITE3_1)
    <REJECTED> -> failed_json (writer SQLITE3_1)
HTTPCaller_Output: Inspector
failed_json (writer SQLITE3_1)
    attributes: url varchar(200), MB06 varchar(7), SITE_ID varchar(80), _response_body varchar(200), _http_status_code varchar(200), summary varchar(200)
results (writer SQLITE3_1)
    attributes: url varchar(200), MB06 varchar(7), SITE_ID varchar(80), _response_body varchar(200), _http_status_code varchar(200), summary varchar(200), json_type varchar(200), json_index varchar(200)
failed_http_call (writer SQLITE3_1)
    attributes: url varchar(200), lat varchar(200), long varchar(200), nztm x varchar(200), nztm y varchar(200), MB06 varchar(7), REGC06 varchar(2), CON06 varchar(4), MCON06 varchar(4), TA06 varchar(3), WARD06 varchar(5), CB06 varchar(5), TASUB06 varchar(5), AU06 varchar(6), UA06 varchar(3), GED02 varchar(3), MED02 varchar(1), TA06V2 varchar(3), WARD06V2 varchar(5), CB06V2 varchar(5), TASUB06V2 varchar(5), _indices{}.x varchar(200), _indices{}.y varchar(200), _indices{}.z varchar(200), OBJECTID integer, SITE_ID varchar(80), DISPLAY_NA varchar(80), AREA_CODE varchar(80), SHOW_ON_MA varchar(80), SITE_TYPE varchar(80),
      SITE_GRADE varchar(80), RAIN_AFFEC varchar(80), SITE_NOT_S varchar(80), WARNING_TE varchar(254), NOTE_TEXT varchar(80), DISPLAY_AR varchar(80), DISPLAY_GR varchar(80), DISPLAY_LI varchar(80), NZMGX real(24,15), NZMGY real(24,15), NZMS260 varchar(80), NZTMX real(24,15), NZTMY real(24,15), NZTOPO50 varchar(80), WGS84_LONG real(24,15), WGS84_LATI real(24,15), SOURCECODE varchar(80), QARCODE integer, CREATEDBY varchar(80), CREATEDDAT varchar(80), MODIFIEDBY varchar(80), MODIFIEDDA varchar(80), SITE_SAMPL varchar(80), _distance varchar(200), _angle varchar(200), _candidate_angle varchar(200), _candidate_label_angle varchar(200), _closest_candidate_x varchar(200), _closest_candidate_y varchar(200), _closest_base_x varchar(200),
      _closest_base_y varchar(200), distance varchar(200), angle varchar(200), candidate_angle varchar(200), candidate_label_angle varchar(200), closest_candidate_x varchar(200), closest_candidate_y varchar(200), closest_base_x varchar(200), closest_base_y varchar(200), _element_index varchar(200), _error varchar(200), _headers{}.name varchar(200), _headers{}.value varchar(200), _response_body varchar(200), _http_status_code varchar(200)
AttributeCreator_Output: Inspector
